FME workspace dbf_dbf_dbf2sqlite3.fmw

Parameters:
- SourceDataset_DBF = D:\TTSIB\ESS\EXPORT\DB001030.DBF   # dBASE (DBF)-Datei(en) der Quelle
- SourceDataset_DBF_5 = D:\TTSIB\ESS\EXPORT\DB000255.DBF   # dBASE (DBF)-Datei(en) der Quelle
- SourceDataset_DBF_4 = D:\TTSIB\ESS\EXPORT\DBABSCHN.DBF   # dBASE (DBF)-Datei(en) der Quelle
- DestDataset_SQLITE3 = $(FME_MF_DIR)daten.db   # SQLite-Datenbank-Datei des Ziels

Readers:
- DBF_1: DBF from $(SourceDataset_DBF)
- DBF_2: DBF from $(SourceDataset_DBF_5)
- DBF_3: DBF from $(SourceDataset_DBF_4)

Writers:
- SQLITE3_1: SQLITE3 to $(DestDataset_SQLITE3)

DB001030 (reader DBF_1)
    attributes: VNK char(10), NNK char(10), VST number(5,0), BST number(5,0), STREIFEN char(1), STREIFENNR number(2,0), ART char(3), ARTOBER char(3), BREITE number(8,0), BISBREITE number(8,0), BLPART char(2), BLPART3 char(5), UIPART char(2), UIPART3 char(5), LAENGE number(7,3), FLAECHE number(5,0), BAUJAHRGEW date, ABNAHMEGEW date, DAUERGEW number(2,0), ABLAUFGEW date, ERFART char(2), QUELLE char(2), ADATUM date, BEMERKUNG char(254), BEARBEITER char(64), STAND date, PARENTID char(32), OBJEKTID char(32), FLAG char(1)
    -> DB001030 (writer SQLITE3_1)
DB001030 (writer SQLITE3_1)
    attributes: VNK varchar(10), NNK varchar(10), VST float, BST float, STREIFEN varchar(1), STREIFENNR float, ART varchar(3), ARTOBER varchar(3), BREITE float, BISBREITE float, BLPART varchar(2), BLPART3 varchar(5), UIPART varchar(2), UIPART3 varchar(5), LAENGE float, FLAECHE float, BAUJAHRGEW text, ABNAHMEGEW text, DAUERGEW float, ABLAUFGEW text, ERFART varchar(2), QUELLE varchar(2), ADATUM text, BEMERKUNG varchar(254), BEARBEITER varchar(64), STAND text, PARENTID varchar(32), OBJEKTID varchar(32), FLAG varchar(1)
DB000255 (reader DBF_2)
    attributes: VNK char(10), NNK char(10), SORT number(8,0), XKOORD number(16,7), YKOORD number(16,7), STAND date, FLAG char(1)
    -> DB000255 (writer SQLITE3_1)
DB000255 (writer SQLITE3_1)
    attributes: VNK varchar(10), NNK varchar(10), SORT float, XKOORD float, YKOORD float, STAND text, FLAG varchar(1)
DBABSCHN (reader DBF_3)
    attributes: VNK char(10), NNK char(10), LEN number(5,0), FLAG char(1)
    -> DBABSCHN (writer SQLITE3_1)
DBABSCHN (writer SQLITE3_1)
    attributes: VNK varchar(10), NNK varchar(10), LEN float, FLAG varchar(1)
